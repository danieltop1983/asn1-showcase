MYMOD DEFINITIONS AUTOMATIC TAGS::= BEGIN

MyInt ::= INTEGER (0 .. 99) /* MyInt */

RGB ::= ENUMERATED 
{
red (100),
green (200),
blue (300),
yellow (400)
}



MyColor ::= SEQUENCE 
{
  a3 MyInt,                   /* a3 */
  colorData CHOICE 
  {
  red INTEGER(1..10),
  green INTEGER (11..20),
  blue INTEGER (21..30),
  yellow MyInt
  }
  
}

END
